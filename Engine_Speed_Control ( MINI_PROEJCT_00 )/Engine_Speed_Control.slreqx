# untitled

## Speed Calculation (Functional)
The engine speed must be calculated using the formula Speed=100X−50Y+400Speed=100X−50Y+400.

## Speed Limiting (Functional)
If the calculated engine speed is above 3000, limit output to 3000. If below 100, limit to 100. Otherwise, output should be the calculated speed.
